RT1170-NETNODE-MIB DEFINITIONS ::= BEGIN

IMPORTS
    MODULE-IDENTITY, OBJECT-TYPE, NOTIFICATION-TYPE, Integer32, Gauge32,
    IpAddress, enterprises
        FROM SNMPv2-SMI
    TruthValue, DisplayString, MacAddress
        FROM SNMPv2-TC
    MODULE-COMPLIANCE, OBJECT-GROUP, NOTIFICATION-GROUP
        FROM SNMPv2-CONF;

rt1170NetNode MODULE-IDENTITY
    LAST-UPDATED "202610180000Z"
    ORGANIZATION "Example"
    CONTACT-INFO "admin@example.com"
    DESCRIPTION
        "Second product built on the PHYTEC phyCORE-i.MX RT1170 SNMPv3 agent:
         LED control plus the state of the Ethernet interface.

         NOTE: enterprise number 26381 is the lwIP project's PEN, used as a
         placeholder. Replace it with your own IANA Private Enterprise Number
         (and APP_SNMP_ENTERPRISE_ID in app_config.h) before deployment."
    REVISION "202610180000Z"
    DESCRIPTION "Initial version: LED control, network interface."
    ::= { enterprises 26381 2 }

rt1170NetNodeNotifications OBJECT IDENTIFIER ::= { rt1170NetNode 0 }
rt1170NetNodeObjects       OBJECT IDENTIFIER ::= { rt1170NetNode 1 }
rt1170NetNodeConformance   OBJECT IDENTIFIER ::= { rt1170NetNode 2 }

led OBJECT IDENTIFIER ::= { rt1170NetNodeObjects 1 }
net OBJECT IDENTIFIER ::= { rt1170NetNodeObjects 2 }

-- LED

ledBlinkEnable OBJECT-TYPE
    SYNTAX      TruthValue
    MAX-ACCESS  read-write
    STATUS      current
    DESCRIPTION "true: LED1 blinks; false: LED1 is off. Stored in the EEPROM."
    ::= { led 1 }

ledBlinkPeriod OBJECT-TYPE
    SYNTAX      Integer32 (50..10000)
    UNITS       "milliseconds"
    MAX-ACCESS  read-write
    STATUS      current
    DESCRIPTION "Full blink period of LED1 (on + off). Stored in the EEPROM."
    ::= { led 2 }

ledState OBJECT-TYPE
    SYNTAX      INTEGER { on(1), off(2) }
    MAX-ACCESS  read-only
    STATUS      current
    DESCRIPTION "Current state of LED1."
    ::= { led 3 }

-- Network interface

netHostname OBJECT-TYPE
    SYNTAX      DisplayString (SIZE (1..32))
    MAX-ACCESS  read-write
    STATUS      current
    DESCRIPTION
        "Host name of the device (letters, digits and '-', not at the start
         or end). Sent to the DHCP server (option 12) and reported as
         sysName. Stored in the EEPROM."
    ::= { net 1 }

netMacAddress OBJECT-TYPE
    SYNTAX      MacAddress
    MAX-ACCESS  read-only
    STATUS      current
    DESCRIPTION "MAC address of the Ethernet interface."
    ::= { net 2 }

netDhcpEnable OBJECT-TYPE
    SYNTAX      TruthValue
    MAX-ACCESS  read-only
    STATUS      current
    DESCRIPTION "true: the address is obtained with DHCP; false: static."
    ::= { net 3 }

netIpAddress OBJECT-TYPE
    SYNTAX      IpAddress
    MAX-ACCESS  read-only
    STATUS      current
    DESCRIPTION "Current IPv4 address (0.0.0.0 while DHCP has no lease)."
    ::= { net 4 }

netSubnetMask OBJECT-TYPE
    SYNTAX      IpAddress
    MAX-ACCESS  read-only
    STATUS      current
    DESCRIPTION "Current IPv4 subnet mask."
    ::= { net 5 }

netGateway OBJECT-TYPE
    SYNTAX      IpAddress
    MAX-ACCESS  read-only
    STATUS      current
    DESCRIPTION "Current IPv4 default gateway."
    ::= { net 6 }

netLinkStatus OBJECT-TYPE
    SYNTAX      INTEGER { up(1), down(2) }
    MAX-ACCESS  read-only
    STATUS      current
    DESCRIPTION "State of the Ethernet link."
    ::= { net 7 }

netLinkSpeed OBJECT-TYPE
    SYNTAX      Gauge32
    UNITS       "Mbit/s"
    MAX-ACCESS  read-only
    STATUS      current
    DESCRIPTION "Negotiated link speed: 10, 100 or 1000; 0 while the link is down."
    ::= { net 8 }

-- Notifications

ledConfigChanged NOTIFICATION-TYPE
    OBJECTS     { ledBlinkEnable, ledBlinkPeriod }
    STATUS      current
    DESCRIPTION "Sent after ledBlinkEnable or ledBlinkPeriod is changed, via
                 SNMP or the web page."
    ::= { rt1170NetNodeNotifications 1 }

netLinkChanged NOTIFICATION-TYPE
    OBJECTS     { netLinkStatus, netLinkSpeed }
    STATUS      current
    DESCRIPTION "Sent when the Ethernet link goes up or down. With a single
                 interface the link-down trap cannot leave the device: only
                 the link-up one reaches the manager."
    ::= { rt1170NetNodeNotifications 2 }

-- Conformance

rt1170NetNodeGroups      OBJECT IDENTIFIER ::= { rt1170NetNodeConformance 1 }
rt1170NetNodeCompliances OBJECT IDENTIFIER ::= { rt1170NetNodeConformance 2 }

rt1170NetNodeLedGroup OBJECT-GROUP
    OBJECTS     { ledBlinkEnable, ledBlinkPeriod, ledState }
    STATUS      current
    DESCRIPTION "LED control objects."
    ::= { rt1170NetNodeGroups 1 }

rt1170NetNodeNetGroup OBJECT-GROUP
    OBJECTS     { netHostname, netMacAddress, netDhcpEnable, netIpAddress,
                  netSubnetMask, netGateway, netLinkStatus, netLinkSpeed }
    STATUS      current
    DESCRIPTION "Network interface objects."
    ::= { rt1170NetNodeGroups 2 }

rt1170NetNodeNotificationGroup NOTIFICATION-GROUP
    NOTIFICATIONS { ledConfigChanged, netLinkChanged }
    STATUS      current
    DESCRIPTION "Notifications."
    ::= { rt1170NetNodeGroups 3 }

rt1170NetNodeCompliance MODULE-COMPLIANCE
    STATUS      current
    DESCRIPTION "Compliance statement for the RT1170 network node."
    MODULE
        MANDATORY-GROUPS { rt1170NetNodeLedGroup, rt1170NetNodeNetGroup,
                           rt1170NetNodeNotificationGroup }
    ::= { rt1170NetNodeCompliances 1 }

END
